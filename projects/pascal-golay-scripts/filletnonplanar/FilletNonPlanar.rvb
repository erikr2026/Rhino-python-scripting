Option Explicit
'Script written by Pascal
' RMA
'Script version Monday, November 07, 2011

Rhino.AddStartUpScript Rhino.LastLoadedScriptFile
Rhino.AddAlias "FilletNonPlanar", "_NoEcho _-Runscript (FilletNonPlanar)"


'fillet two non-coplanar curves with
' a fillet arc deformed in the arc plane normal

Private oldrad

If isEmpty(oldrad) Then
	oldrad = 1
End If

'Call FilletNonPlanar()


Sub FilletNonPlanar()
	
	Dim dblRad: dblrad = Rhino.GetReal("Fillet radius.", OldRad)
	If isNull(dblRad) Then Exit Sub
	Oldrad = dblrad
	
	Dim aCrvs(1)
	
	'keep track of curve flipping so direction can be restored at the end.
	Dim flip1, flip2
	flip1 = False
	flip2 = False
	
	'get the curves and pick parameters
	aCrvs(0) = Rhino.GetCurveObject("Select the first curve near the end to fillet.", False)
	If Not isArray(aCrvs(0)) Then  Exit Sub
	
	Dim sCrv1: sCrv1 = aCrvs(0)(0)
	Dim LineArray1, LineArray2
	If Rhino.IsLine(sCrv1) Then LineArray1 = array(Rhino.CurveStartPoint(sCrv1), Rhino.CurveEndPoint(sCrv1))
	
	'find which end of the curve was picked and
	'if the start point, flip the curve.
	Dim CrvEnd1:CrvEnd1 = GetCrvEnd(sCrv1, aCrvs(0)(4))
	If CrvEnd1 = 0 Then 
		Rhino.ReverseCurve sCrv1
		flip1 = True
	End If
	
	aCrvs(1) = Rhino.GetCurveObject("Select the second curve near the end to fillet.", False)
	If Not isArray(aCrvs(1)) Then  Exit Sub
	
	Dim sCrv2: sCrv2 = aCrvs(1)(0)
	Dim CrvEnd2:CrvEnd2 = GetCrvEnd(sCrv2, aCrvs(1)(4))
	
	If CrvEnd2 = 0 Then 
		Rhino.ReverseCurve sCrv2
		flip2 = True
	End If
	If Rhino.IsLine(sCrv2) Then LineArray2 = array(Rhino.CurveStartPoint(sCrv2), Rhino.CurveEndPoint(sCrv2))
	
	
	Rhino.EnableRedraw False
	
	'find a best fit plane from the input curve tangents.
	Dim Plane, vecDir
	': Plane = Rhino.ViewCPlane()
	Plane = AutoPlane(array(sCrv1, sCrv2))
	
	'DrawPlaneFrame Plane, 100
	
	vecDir = Plane(3)
	'make a transform to project the inputs to the plane
	Dim XForm: xform = Rhino.XformPlanarProjection(Plane)
	
	'Project copies to the plane
	Dim Flat1, Flat2
	Flat1 = Rhino.TransformObject(sCrv1, Xform, True)
	Flat2 = Rhino.TransformObject(sCrv2, Xform, True)
	
	Dim intFlat: intFlat = Rhino.CurveCurveIntersection(Flat1, Flat2)
	
	'if there is no curve intersection from the projected inputs,
	'and the inputs are lines, make new temp lines to fillet
	If Not isArray(intFlat) Then
		If Rhino.IsLine(Flat1) And Rhino.IsLine(Flat2) Then
			Dim Crvtan1, Crvtan2, temp1, temp2, tl1, tl2

			tl1 = array(Rhino.CurveStartPoint(Flat1), Rhino.CurveEndPoint(Flat1))
			tl2 = array(Rhino.CurveStartPoint(Flat2), Rhino.CurveEndPoint(Flat2))
			
			intFlat = Rhino.PlaneClosestPoint(Plane, Rhino.LineLineIntersection(tl1, tl2, False)(0))
			temp1 = Rhino.AddLine(Rhino.CurveStartPoint(Flat1), intFlat)
			temp2 = Rhino.AddLine(Rhino.CurveStartPoint(Flat2), intFlat)
			Rhino.DeleteObjects array(Flat1, Flat2)
			Flat1 = temp1
			Flat2 = temp2
		

		End If
	End If
	
	Dim ftPts
	
	'find fillet points and add the fillet arc to the 2d curves.
	ftPts = Rhino.CurveFilletPoints(Flat1, Flat2, dblrad, aCrvs(0)(3), aCrvs(1)(3))
	
	If Not isArray(ftPts) Then

		Rhino.DeleteObjects(array(Flat1, Flat2))
		Rhino.Enableredraw True
		Rhino.Print "Fillet failed. Curve ends may be too far apart for the chosen radius."
		Exit Sub
	End If
	
	Dim sFt: sFt = Rhino.AddFilletCurve(Flat1, Flat2, dblRad, Rhino.EvaluateCurve(Flat1, Rhino.CurveClosestPoint(Flat1, aCrvs(0)(3))), Rhino.EvaluateCurve(Flat2, Rhino.CurveClosestPoint(Flat2, aCrvs(1)(3))))

	'bail if the fillet cannot be made
	If  isNull(sFt) Then
		Rhino.EnableRedraw True
		If Flip1 = True Then Rhino.ReverseCurve sCrv1
		If Flip2 = True Then Rhino.ReverseCurve sCrv2
		Exit Sub
		
	End If
	
	'change the fillet curve degree to 3 to ensure at least 4 points.
	Rhino.UnselectAllObjects()
	Rhino.SelectObject sFt
	Rhino.Command "_NoEcho _ChangeDegree " & 3 
	
	'delete the 2d inputs
	Rhino.DeleteObjects array(Flat1, Flat2)
	
	Dim Line1, Line2
	'find lines normal to the plane at the fillet curve end points.
	Line1 = array(ftPts(0), Rhino.PointAdd(ftPts(0), VecDir))
	Line2 = array(ftPts(Ubound(ftPts)), Rhino.PointAdd(ftPts(Ubound(ftPts)), VecDir))
	Line2 = array(Rhino.CurveEndPoint(sft), Rhino.PointAdd(Rhino.CurveEndPoint(sft), VecDir))
	
	Dim aInt1, aint2
	
	'intersect the lines and the curves. This is a projection
	'of the 2d fillet ends to the 3d inputs, in the plane normal
	If Rhino.IsLine(sCrv1) Then
		aInt1 = Rhino.LineLineIntersection(Line1, LineArray1, False)(0)
	Else
		aInt1 = Rhino.LineCurveIntersection(Line1, sCrv1, Rhino.UnitAbsoluteTolerance())	
	End If
	
	Dim vecLine: vecLine = rhino.VectorCreate(Line2(0), Line2(1))
	
	If Rhino.IsLine(sCrv2) Then
		aInt2 = Rhino.LineLineIntersection(Line2, LineArray2, False)(0)
	Else
		Rhino.ObjectColor sCrv2, vbMagenta
		Rhino.ObjectColor sFt, vbBlue
		aInt2 = Rhino.LineCurveIntersection(Line2, sCrv2, 10 * Rhino.UnitAbsoluteTolerance())	
	End If

	If  Not isArray(aInt1) Or Not IsArray(aInt2) Then
		
		Rhino.EnableRedraw True
		If Flip1 = True Then Rhino.ReverseCurve sCrv1
		If Flip2 = True Then Rhino.ReverseCurve sCrv2
		Exit Sub
		
	End If
	
	Dim aSplit1, aSplit2
	
	'split the input curves with the line-curve intersectioin.
	Dim intPar1, intpar2, intpt1, intpt2
	If arrayDimensions(aInt1) > 1 Then
		intPar1 = aInt1(0, 7)
		Intpt1 = Rhino.EvaluateCurve(sCrv1, intpar1)
	Else
		intPt1 = aInt1
		intPar1 = Rhino.CurveClosestPoint(sCrv1, aint1)
	End If
	
	aSplit1 = Rhino.SplitCurve(sCrv1, intpar1)
	
	If arrayDimensions(aInt2) > 1 Then
		intPar2 = aInt2(0, 7)
		Intpt2 = Rhino.EvaluateCurve(sCrv2, intpar2)
	Else
		intPt2 = aInt2
		intPar2 = Rhino.CurveClosestPoint(sCrv2, aint2)
	End If
		
	aSplit2 = Rhino.SplitCurve(sCrv2, intPar2)

	'delete the parts of the curve that are not needed.
	Dim temp
	If isArray(aSplit1) Then
		If Ubound(aSplit1) > 0 Then	
			sCrv1 = DeleteCurveEnd(aSplit1, 1)
		Else
			sCrv1 = aSplit1(0)
		End If
			
	Else
		If Rhino.IsLine(sCrv1) Then
			temp = Rhino.AddLine(Line1Array(0), intPt1)
			Rhino.MatchObjectAttributes temp, sCrv1
			Rhino.DeleteObject sCrv1
			sCrv1 = temp
		End If
	End If
	
		
	If isArray(aSplit2) Then
		If Ubound(aSplit2) > 0 Then	
			sCrv2 = DeleteCurveEnd(aSplit2, 1)
		Else
			sCrv2 = aSplit2(0)
		End If
	Else
		If Rhino.IsLine(sCrv2) Then
			temp = Rhino.AddLine(Line2Array(0), intPt2)
			Rhino.MatchObjectAttributes temp, sCrv2
			Rhino.DeleteObject sCrv2
			sCrv2 = temp
		End If
	End If
	
	Dim ftStart, ftEnd
	
	'the fillet curve end points
	ftStart = Rhino.CurveStartPoint(sFt)
	ftEnd = Rhino.CurveEndPoint(sFt)
	
	'the trimmed input curve end points
	Dim targ1, targ2
	
	targ1 = aInt1'(0, 3)
	targ2 = aInt2'(0, 3)
	
	Dim vecTan1, vecTan2, dist1, dist2
	
	'the input curve tangent vectors
	Dim q: q = Rhino.CurveDomain(sCrv1)
	vectan1 = Rhino.CurveTangent(sCrv1, Rhino.CurveDomain(sCrv1)(1))
	vectan2 = Rhino.CurveTangent(sCrv2, Rhino.CurveDomain(sCrv2)(1))
	
	'get the 2d fillet curve point locations
	Dim ftCV: ftCV = Rhino.CurvePoints(sFt)
	Dim Bound: Bound = Ubound(ftCV)
	
	'find the current distance from the 2d fillet ends to the second points.
	'find a corresponding  location off the ends of the 3d inputs
	dist1 = Rhino.Distance(ftCV(0), ftCV(1))
	targ1 = Rhino.PointAdd(Rhino.CurveEndPoint(sCrv1), Rhino.VectorScale(vectan1, dist1))
	
	dist2 = Rhino.Distance(ftCV(Bound), ftCV(bound - 1))
	targ2 = Rhino.PointAdd(Rhino.CurveEndPoint(sCrv2), Rhino.VectorScale(vecTan2, dist2))	

	'turn on the fillet control points
	Rhino.EnableObjectGrips sFt
	
	'an array of points for the fillet end and second points as
	'well as inputs to a best fit plane.

	Dim cnt1: cnt1 = Rhino.CurvePointCount(sCrv1)

	Rhino.ObjectGripLocation sFt, 0, Rhino.CurveEndPoint(sCrv1)

	targ1 = Rhino.PointAdd(Rhino.CurveStartPoint(sFt), Rhino.VectorScale(vectan1, dist1))
	Rhino.ObjectGripLocation sFt, 1, targ1
	Rhino.ObjectGripLocation sFt, Bound, Rhino.CurveEndPoint(sCrv2)
	targ2 = Rhino.PointAdd(Rhino.CurveEndPoint(sFt), Rhino.VectorScale(vectan2, dist2))
	Rhino.ObjectGripLocation sFt, Bound - 1, targ2
	
	'if the fillet has more than 4 points (angle<90) then
	'move the middle points to the best fit plane of the 
	'end and tangent points.
	
	Dim aLoc(3)
	aLoc(0) = targ1
	aLoc(1) = Rhino.CurveStartPoint(sFt)
	aloc(2) = targ2
	aloc(3) = Rhino.CurveEndPoint(sFt)
	
	If Bound > 3 Then

		Dim i
		Dim testPlane: testPlane = Rhino.PlaneFitFromPoints(aLoc)
		'		DrawPlaneFrame testPlane, 10
	
		For i = 2 To bound - 2
			
			Rhino.ObjectGripLocation sFt, i, Rhino.PlaneClosestPoint(testPlane, Rhino.ObjectGripLocation(sFt, i))
			
		Next
		
	End If
	
	'turn off ther fillet grips, clean up, and redraw.
	Rhino.EnableObjectGrips sFt, False
	If Flip1 = True Then Rhino.ReverseCurve sCrv1
	If Flip2 = True Then Rhino.ReverseCurve sCrv2
	Rhino.SelectObject sFt
	Rhino.EnableRedraw True
	
End Sub


Function GetCrvEnd(crv, t)
	'0 = Start, 1 = End
	Dim Dom: dom = Rhino.CurveDomain(crv)
	If Abs(t - dom(0)) > Abs(t - dom(1)) Then
		GetCrvEnd = 1
	Else
		GetCrvEnd = 0
	End If
End Function


Function DeleteCurveEnd(aCrv, IntEnd)
	
	Dim aDom1, aDom2

	aDom1 = Rhino.CurveDomain(acrv(0))
	aDom2 = Rhino.CurveDomain(acrv(1))	

	If aDom1(1) < aDom2(1) Then
		If intEnd = 1 Then
			Rhino.DeleteObject(aCrv(1))
			DeleteCurveEnd = aCrv(0)
		Else
			Rhino.DeleteObject(aCrv(0))
			DeleteCurveEnd = aCrv(1)
		End If
	Else
		If intEnd = 1 Then
			Rhino.DeleteObject(aCrv(0))
			DeleteCurveEnd = aCrv(1)
		Else
			Rhino.DeleteObject(aCrv(1))
			DeleteCurveEnd = aCrv(0)
		End If
		
	End If

End Function


Function AveragePoints(aPts)
	'Finds the average coordinates of an array
	'of points.

	Dim X, Y, Z
	Dim i
	
	X = 0
	Y = 0
	Z = 0

	For i=0 To UBound(aPts)
			
		'add all the X values
		X = X + aPts(i)(0)
	
		'add all th Y values
		Y = Y + aPts(i)(1)			
	
		'add all the Z values
		Z = Z + apts(i)(2)
	Next
	
	'Divide by the number of points to
	'get the average  for each
	'create the output array from the 3 averages
	AveragePoints = array(X / (UBound(aPts) + 1), Y / (UBound(aPts) + 1), Z / (UBound(aPts) + 1))

End Function


Function AutoPlane(acrvs)
		
	Dim test_pt: test_pt = Rhino.CurveClosestObject(aCrvs(0), array(aCrvs(1)))
	
	If isArray(test_pt) Then
		Dim av_pt: av_pt = AveragePoints(array(test_pt(1), test_pt(2)))
	End If
	
	Dim t1, t2, p1,p2
	
	t1 = Rhino.CurveClosestPoint(aCrvs(0), test_pt(1))
	t2 = Rhino.CurveClosestPoint(aCrvs(1), test_pt(2))
	P1 = Rhino.PointAdd(av_pt, Rhino.CurveTangent(aCrvs(0), t1))
	p2 = Rhino.PointAdd(av_pt, Rhino.CurveTangent(aCrvs(1), t2))
	
	autoPlane = Rhino.PlaneFitFromPoints(array(av_pt, p1, p2))

End Function



Function ArrayDimensions(theArray)
	Dim Result,test
	Result = 0
	If isarray(theArray) Then
		On Error Resume Next
		Do
			test = -2
			test = ubound(theArray, result + 1)
			If test > -2 Then result = result + 1
		Loop Until test = -2
		On Error GoTo 0
	End If
	ArrayDimensions = Result
End Function

Sub DrawPlaneFrame (aPlane, dblScale)
	
	'FOR TESTING
	
	If isNull(dblScale) Then dblScale = 1
	Rhino.EnableRedraw(False)
	
	Dim pt0: Pt0 = aPlane(0)
	Dim aLines(5)
	
	Dim vec1: vec1 = Rhino.VectorScale(aPlane(1), dblScale)
	Dim pt1: Pt1 = Rhino.PointAdd(Pt0, vec1)
	Dim Pt4: Pt4 = Rhino.PointAdd(Pt0, Rhino.VectorReverse(Vec1))

	Dim vec2: vec2 = Rhino.VectorScale(aPlane(2), dblScale)
	Dim pt2: Pt2 = Rhino.PointAdd(Pt0, Vec2)	
	Dim Pt5: Pt5 = Rhino.PointAdd(Pt0, Rhino.VectorReverse(Vec2))
	Dim vec3: vec3 = Rhino.VectorScale(aPlane(3), dblScale)
	Dim pt3: Pt3 = Rhino.PointAdd(Pt0, Vec3)	
	Dim Pt6: Pt6 = Rhino.PointAdd(Pt0, Rhino.VectorReverse(Vec3))
	
	aLines(0) = Rhino.AddLine(Pt0, Pt1)
	aLines(1) = Rhino.AddLine(Pt0, pt2)
	aLines(2) = Rhino.AddLine(Pt0, Pt3)
	aLines(3) = Rhino.AddLine(Pt0, Pt4)
	aLines(4) = Rhino.AddLine(Pt0, Pt5)
	aLines(5) = Rhino.AddLine(Pt0, Pt6)
	
	Rhino.ObjectColor array(alines(0), alines(3)), vbred
	Rhino.ObjectColor array(alines(1), alines(4)), vbgreen
	rhino.ObjectColor array(alines(2), alines(5)), vbBlue
	
	Dim i
	For i = 0 To 2
		Rhino.CurveArrows aLines(i), 2
	Next
			
	Dim sgrp: sGrp = Rhino.AddGroup
	
	Rhino.AddObjectsToGroup aLines, sGrp
	Rhino.EnableRedraw(True)
	
End Sub
